CCSDS-SLE-TRANSFER-SERVICE-COMMON-TYPES
{  iso identified-organization(3)
   standards-producing-organization(112) ccsds(4)
   space-link-extension(3) sle-transfer-services(1)
   modules(1) common-modules(99) version-five(5) asn1-common-types(1)
}
DEFINITIONS
IMPLICIT TAGS
::=   BEGIN
EXPORTS  ConditionalTime
,        Credentials
,        DeliveryMode
,        Diagnostics
,        Duration
,        ForwardDuStatus
,        IntPosLong
,        IntPosShort
,        IntUnsignedLong
,        IntUnsignedShort
,        InvokeId
,        ParameterName
,        SlduStatusNotification
,        SpaceLinkDataUnit
,        Time
;
ConditionalTime          ::=    CHOICE
{ undefined          [0]     NULL
, known              [1]    Time
}
-- If credentials are used, it will be necessary that
-- the internal structure of the octet string is known
-- to both parties. Since the structure will depend on
-- algorithm used, it is not specified here. However,
-- the peer entities may use ASN.1 encoding to make the
-- internal structure visible.
Credentials              ::=    CHOICE
{ unused             [0]    NULL
, used                [1]    OCTET STRING (SIZE (8 .. 256))
}
DeliveryMode             ::=    INTEGER
{ rtnTimelyOnline                  (0)
, rtnCompleteOnline                (1)
, rtnOffline                       (2)
, fwdOnline                        (3)
, fwdOffline                       (4)
}

Diagnostics             ::=   INTEGER
{ duplicateInvokeId              (100)
, otherReason                    (127)
}
-- The Duration is expressed in microseconds
Duration                ::=   IntUnsignedLong
ForwardDuStatus         ::=   INTEGER
{ radiated                       (0)
, expired                        (1)
, interrupted                    (2)
, acknowledged                   (3)    -- FSP
, productionStarted              (4)    -- CLTU: 'radiation started'
, productionNotStarted           (5)    -- CLTU: 'radiation not started'
, unsupportedTransmissionMode    (6)    -- FSP
}
-- 1 to (2^32)-1
IntPosLong              ::=   INTEGER (1 .. 4294967295)
-- 1 to (2^16)-1
IntPosShort             ::=   INTEGER (1 .. 65535)
-- 0 to (2^32)-1
IntUnsignedLong         ::=   INTEGER (0 .. 4294967295)
-- 0 to (2^16)-1
IntUnsignedShort        ::=   INTEGER (0 .. 65535)
InvokeId                ::=   IntUnsignedShort

ParameterName                       ::=    INTEGER
{ acquisitionSequenceLength                (201)
, apidList                                 (2)
, bitLockRequired                          (3)
, blockingTimeoutPeriod                    (0)
, blockingUsage                            (1)
, bufferSize                               (4)
, clcwGlobalVcId                           (202)
, clcwPhysicalChannel                      (203)
, copCntrFramesRepetition                  (300)
, deliveryMode                             (6)
, directiveInvocation                      (7)
, directiveInvocationOnline                (108)
, expectedDirectiveIdentification          (8)
, expectedEventInvocationIdentification    (9)
, expectedSlduIdentification               (10)
, fopSlidingWindow                         (11)
, fopState                                 (12)
, latencyLimit                             (15)
, mapList                                  (16)
, mapMuxControl                            (17)
, mapMuxScheme                             (18)
, maximumFrameLength                       (19)
, maximumPacketLength                      (20)
, maximumSlduLength                        (21)
, minimumDelayTime                         (204)
, minReportingCycle                        (301)
, modulationFrequency                      (22)
, modulationIndex                          (23)
, notificationMode                         (205)
, permittedControlWordTypeSet              (101)
, permittedFrameQuality                    (302)
, permittedGvcidSet                        (24)
, permittedTcVcidSet                       (102)
, permittedTransmissionMode                (107)
, permittedUpdateModeSet                   (103)
, plop1IdleSequenceLength                  (206)
, plopInEffect                             (25)
, protocolAbortMode                        (207)
, reportingCycle                           (26)
, requestedControlWordType                 (104)
, requestedFrameQuality                    (27)
, requestedGvcid                           (28)
, requestedTcVcid                          (105)
, requestedUpdateMode                      (106)
, returnTimeoutPeriod                      (29)
, rfAvailable                              (30)
, rfAvailableRequired                      (31)
, segmentHeader                            (32)
, sequCntrFramesRepetition                 (303)
, subcarrierToBitRateRatio                 (34)
, throwEventOperation                      (304)
, timeoutType                              (35)
, timerInitial                             (36)
, transmissionLimit                        (37)
, transmitterFrameSequenceNumber           (38)
, vcMuxControl                             (39)
, vcMuxScheme                              (40)
, virtualChannel                           (41)
}

SlduStatusNotification ::=      INTEGER
{ produceNotification              (0)
, doNotProduceNotification         (1)
}

SpaceLinkDataUnit        ::=    OCTET STRING (SIZE (1 .. 65536))

Time                      ::=   CHOICE
{ ccsdsFormat         [0]    TimeCCSDS
, ccsdsPicoFormat     [1]    TimeCCSDSpico
}


TimeCCSDS                 ::=   OCTET STRING (SIZE(8))
-- P-field is implicit (not present, defaulted to 41 hex
-- T-field:
-- 2 octets: number of days since 1958/01/01 00:00:00
-- 4 octets: number of milliseconds of the day
-- 2 octets: number of microseconds of the millisecond
--         (set to 0 if not used)
-- This definition reflects exactly the format of the CCSDS defined
-- time tag as used in spacelink data units (see reference [7]).
TimeCCSDSpico            ::=    OCTET STRING (SIZE(10))
-- P-field is implicit (not present, defaulted to 42 hex
-- T-field:
-- 2 octets: number of days since 1958/01/01 00:00:00
-- 4 octets: number of milliseconds of the day
-- 4 octets: number of picoseconds of the millisecond
--         (set to 0 if not used)
-- This definition reflects exactly the format of the CCSDS defined
-- time tag as used in spacelink data units (see reference [7]).
END

CCSDS-SLE-TRANSFER-SERVICE-BIND-TYPES
{  iso identified-organization(3)
   standards-producing-organization(112) ccsds(4)
   space-link-extension(3) sle-transfer-services(1)
   modules(1) common-modules(99) version-four(4) asn1-bind-types(2)
}
DEFINITIONS
IMPLICIT TAGS
::=   BEGIN
EXPORTS  SleBindInvocation
,        SleBindReturn
,        SlePeerAbort
,        SleUnbindInvocation
,        SleUnbindReturn
;
IMPORTS Credentials
,        IntPosShort
   FROM CCSDS-SLE-TRANSFER-SERVICE-COMMON-TYPES
         ServiceInstanceIdentifier
   FROM CCSDS-SLE-TRANSFER-SERVICE-SERVICE-INSTANCE-ID
;
-- =============================================================
-- The first part of the module definition contains the SLE-PDUs
-- =============================================================
SleBindInvocation          ::=   SEQUENCE
{ invokerCredentials          Credentials
, initiatorIdentifier         AuthorityIdentifier
, responderPortIdentifier     PortId
, serviceType                 ApplicationIdentifier
, versionNumber               VersionNumber
, serviceInstanceIdentifier ServiceInstanceIdentifier
}
SleBindReturn           ::=   SEQUENCE
{ performerCredentials     Credentials
, responderIdentifier      AuthorityIdentifier
, result                   CHOICE
   { positive           [0]   VersionNumber
   , negative           [1]   BindDiagnostic
   }
}
SlePeerAbort            ::=   PeerAbortDiagnostic

SleUnbindInvocation     ::=    SEQUENCE
{ invokerCredentials       Credentials
, unbindReason             UnbindReason
}
SleUnbindReturn         ::=    SEQUENCE
{ responderCredentials     Credentials
, result                    CHOICE
   { positive           [0]    NULL
   }
}
-- =============================================================
-- The second part of the module definition contains the types
-- used by the SLE-PDUs declared in the first part.
-- =============================================================
ApplicationIdentifier      ::=    INTEGER
{ rtnAllFrames                 (0)
, rtnInsert                    (1)
, rtnChFrames                  (2)
-- rtnChFrames includes rtnMcFrames and rtnVcFrames
, rtnChFsh                     (3)
-- rtnChFsh includes rtnMcFsh and rtnVcFsh
, rtnChOcf                     (4)
-- rtnChOcf includes rtnMcOcf and rtnVcOcf
, rtnBitstr                    (5)    -- AOS
, rtnSpacePkt                  (6)
, fwdAosSpacePkt               (7)
, fwdAosVca                    (8)
, fwdBitstr                    (9)
, fwdProtoVcdu                 (10)
, fwdInsert                    (11)
, fwdCVcdu                     (12)
, fwdTcSpacePkt                (13) -- conventional telecommand
, fwdTcVca                     (14) -- conventional telecommand
, fwdTcFrame                   (15)
, fwdCltu                      (16)
}
AuthorityIdentifier     ::=    IdentifierString (SIZE (3 .. 16))
BindDiagnostic                    ::=     INTEGER
{ accessDenied                        (0)
, serviceTypeNotSupported             (1)
, versionNotSupported                 (2)
, noSuchServiceInstance               (3)
, alreadyBound                        (4)
, siNotAccessibleToThisInitiator      (5)
, inconsistentServiceType             (6)
, invalidTime                         (7)
, outOfService                        (8)
, otherReason                         (127)
}
IdentifierString        ::=    VisibleString (FROM (ALL EXCEPT " "))
LogicalPortName         ::=    IdentifierString (SIZE (1 .. 128))

PeerAbortDiagnostic           ::=    INTEGER
{ accessDenied                   (0)
, unexpectedResponderId          (1)
, operationalRequirement         (2)
, protocolError                  (3)
, communicationsFailure          (4)
, encodingError                  (5)
, returnTimeout                  (6)
, endOfServiceProvisionPeriod    (7)
, unsolicitedInvokeId            (8)
, otherReason                    (127)
-- The range of this INTEGER shall be (0 .. 255).
-- (128 .. 255) is reserved for diagnostic codes
-- that are specific to the communications technology used.
}

PortId               ::=   LogicalPortName
UnbindReason         ::=   INTEGER
{ end                   (0)
, suspend               (1)
, versionNotSupported (2)
, other                 (127)
}
VersionNumber        ::=   IntPosShort
END

CCSDS-SLE-TRANSFER-SERVICE-COMMON-PDUS
{  iso identified-organization(3)
   standards-producing-organization(112) ccsds(4)
   space-link-extension(3) sle-transfer-services(1)
   modules(1) common-modules(99) version-four(4) asn1-common-pdu(3)
}
DEFINITIONS
IMPLICIT TAGS
::=   BEGIN
EXPORTS  ReportingCycle
,        SleAcknowledgement
,        SleScheduleStatusReportInvocation
,        SleScheduleStatusReportReturn
,        SleStopInvocation
;
IMPORTS Credentials
,        Diagnostics
,        InvokeId
   FROM CCSDS-SLE-TRANSFER-SERVICE-COMMON-TYPES
;
-- =============================================================
-- The first part of the module definition contains the SLE-PDUs
-- =============================================================
SleAcknowledgement      ::=    SEQUENCE
{ credentials              Credentials
, invokeId                 InvokeId
, result                    CHOICE
   { positiveResult     [0]    NULL
   , negativeResult     [1]    Diagnostics
   }
}
SleScheduleStatusReportInvocation     ::=    SEQUENCE
{ invokerCredentials                      Credentials
, invokeId                                InvokeId
, reportRequestType                       ReportRequestType
}
SleScheduleStatusReportReturn ::=     SEQUENCE
{ performerCredentials            Credentials
, invokeId                        InvokeId
, result                           CHOICE
   { positiveResult            [0]    NULL
   , negativeResult            [1]    DiagnosticScheduleStatusReport
   }
}

SleStopInvocation       ::=    SEQUENCE
{ invokerCredentials       Credentials
, invokeId                 InvokeId
}
-- =============================================================
-- The second part of the module definition contains the types
-- used by the SLE-PDUs declared in the first part.
-- =============================================================
DiagnosticScheduleStatusReport    ::=    CHOICE
{ common                       [0]    Diagnostics
, specific                     [1]    INTEGER
   { notSupportedInThisDeliveryMode      (0)   -- not used for
                                                -- version 1 forward transfer
                                                -- services
   ,     alreadyStopped                  (1)
   ,     invalidReportingCycle           (2)
   }
}
-- The cycle duration is expressed in seconds
ReportingCycle          ::=    INTEGER (2 .. 600)
ReportRequestType       ::=    CHOICE
{ immediately        [0]   NULL
, periodically       [1]   ReportingCycle
, stop               [2]    NULL
}
END

CCSDS-SLE-TRANSFER-SERVICE-SERVICE-INSTANCE-ID
{  iso identified-organization (3) standards-producing-organization(112)
   ccsds(4) space-link-extension(3) sle-transfer-services(1)
   modules(1) common-modules(99) version-five(5)
   asn1-service-id-type(4)
}
DEFINITIONS
IMPLICIT TAGS
::= BEGIN
EXPORTS ServiceInstanceIdentifier
;
-- Object Identifiers definition
sagr     OBJECT IDENTIFIER    ::=    {iso 3 112 4 3 1 2 52}
spack    OBJECT IDENTIFIER    ::=    {iso 3 112 4 3 1 2 53}
fsl-fg   OBJECT IDENTIFIER    ::=    {iso 3 112 4 3 1 2 14}
rsl-fg   OBJECT IDENTIFIER    ::=    {iso 3 112 4 3 1 2 38}
cltu     OBJECT IDENTIFIER    ::=    {iso 3 112 4 3 1 2 7}
fsp      OBJECT IDENTIFIER    ::=    {iso 3 112 4 3 1 2 10}
raf      OBJECT IDENTIFIER    ::=    {iso 3 112 4 3 1 2 22}
rcf      OBJECT IDENTIFIER    ::=    {iso 3 112 4 3 1 2 46}
rcfsh    OBJECT IDENTIFIER    ::=    {iso 3 112 4 3 1 2 44}
rocf     OBJECT IDENTIFIER    ::=    {iso 3 112 4 3 1 2 49}
rsp      OBJECT IDENTIFIER    ::=    {iso 3 112 4 3 1 2 40}
tcf      OBJECT IDENTIFIER    ::=    {iso 3 112 4 3 1 2 12}
tcva     OBJECT IDENTIFIER    ::=    {iso 3 112 4 3 1 2 16}
CCSDS 911.1-B-4                   Page A-11                       August 2016
             CCSDS RECOMMENDED STANDARD FOR SLE RAF SERVICE
-- +++++++++++++++++++++++++++++++++++++
-- +++++++++++++++++++++++++++++++++++++
-- The Service Instance Identifier is a concatenation of Attributes.
-- Each Attribute is composed of a name and a value.
-- Note that the Attribute names are not specified by the ASN.1 proper,
-- but by means of comments in this module.
-- The following Attributes identify the Service Instance:
-- Service agreement
--    the name of which is:   "sagr",
--    the value of which is to be agreed between the user and the provider;
-- Service package
--    the name of which is:   "spack",
--    the value of which is to be agreed between the user and the provider;
-- Forward/Return Service Functional Group
--    the name of which is:
--       "fsl-fg" for the forward services,
--    or:
--       "rsl-fg" for the return services,
--    the value of which is to be agreed between the user and the provider;
-- Service Name identifier,
--       the name of which is:   "cltu"
--       the value of which is: "cltu" plus an instance number;
--    or:
--       the name of which is:   "fsp",
--       the value of which is: "fsp" plus an instance number;
--    or:
--       the name of which is:   "tcva",
--       the value of which is: "tcva" plus an instance number;
--    or:
--       the name of which is:   "tcf",
--       the value of which is: "tcf" plus an instance number;
--    or:
--       the name of which is:   "raf",
--       the value ofwhich is:   "onlc" or "onlt" or "offl" plus an
--       instance number;
--    or:
--       the name of which is:   "rcf",
--       the value of which is: "onlc" or "onlt" or "offl" plus an
--       instance number;
--    or:
--       the name of which is:   "rocf",
--       the value of which is: "onlc" or "onlt" or "offl" plus an
--       instance number;
--    or:
--       the name of which is:   "rcfsh",
--       the value of which is: "onlc" or "onlt" or "offl" plus an
--       instance number;
--    or:
--       the name of which is:   "rsp",
--       the value of which is: "onlc" or "onlt" or "offl" plus an
--       instance number.
--
-- To obtain the string correponding to the instance identifier, one must
-- concatenate the Attributes values and Names as follows:
-- ‘Atribute Name"="Attrbute value’.
-- Two Attributes must be separated by a ".".
--
-- Example: ‘sagr=xyz.spack=abcdef.rsl-fg=gfjdy.raf=onlc2’
-- Note that the quotes are not part of the string.

ATTRIBUTE             ::=   CLASS
{ &id                    OBJECT IDENTIFIER UNIQUE
}
WITH SYNTAX { ID  &id }
GeneralAttributes ATTRIBUTE    ::=
{ serviceAgreement
| servicePackage
| forwardService
| returnService
}
ServiceInstanceAttribute    ::=       SET SIZE(1) OF SEQUENCE
{ identifier                          ATTRIBUTE.&id
                                      ({ServiceInstanceAttributes})
,  siAttributeValue                   VisibleString (SIZE (1 .. 256))
}
ServiceInstanceAttributes ATTRIBUTE ::=
{ GeneralAttributes
| ServiceNames
}
ServiceInstanceIdentifier   ::=   SEQUENCE OF ServiceInstanceAttribute
ServiceNames ATTRIBUTE   ::=
{ rafService
| rcfService
| rcfshService
| rocfService
| rspService
| cltuService
| fspService
| tcfService
| tcvaService
}
-- +++++++++++++++++++++++++++++++++++++
-- CLTU Service Definition
-- The cltu Service Id starts with "cltu" and is
-- followed by the instance number.
cltuService ATTRIBUTE       ::=   { ID cltu }
-- +++++++++++++++++++++++++++++++++++++
-- Forward Service Definition
forwardService ATTRIBUTE    ::=   { ID fsl-fg     }
-- +++++++++++++++++++++++++++++++++++++
-- FSP Service Definition
-- The fsp Service Id starts with "fsp" and is
-- followed by the instance number.
fspService ATTRIBUTE        ::=   { ID fsp     }
-- +++++++++++++++++++++++++++++++++++++
-- RAF Service Definition
-- The raf Service Id starts with "onlc" or "onlt" or "offl" and is
-- followed by the instance number.
rafService ATTRIBUTE        ::=   { ID raf     }
CCSDS 911.1-B-4                    Page A-13                        August 2016
             CCSDS RECOMMENDED STANDARD FOR SLE RAF SERVICE
-- +++++++++++++++++++++++++++++++++++++
-- RCF Service Definition
-- The rcf Service Id starts with "onlc" or "onlt" or "offl" and is
-- followed by the instance number.
rcfService ATTRIBUTE       ::=   { ID rcf     }
-- +++++++++++++++++++++++++++++++++++++
-- RCFSH Service Definition
-- The rcfsh Service Id starts with "onlc" or "onlt" or "offl" and is
-- followed by the instance number.
rcfshService ATTRIBUTE     ::=   { ID rcfsh }
-- +++++++++++++++++++++++++++++++++++++
-- Return Service Definition
returnService ATTRIBUTE    ::=   { ID rsl-fg     }
-- +++++++++++++++++++++++++++++++++++++
-- ROCF Service Definition
-- The rocf Service Id starts with "onlc" or "onlt" or "offl" and is
-- followed by the instance number.
rocfService ATTRIBUTE      ::=   { ID rocf }
-- +++++++++++++++++++++++++++++++++++++
-- RSP Service Definition
-- The rocf Service Id starts with "onlc" or "onlt" or "offl" and is
-- followed by the instance number.
rspService ATTRIBUTE    ::=    { ID rsp     }
-- +++++++++++++++++++++++++++++++++++++
-- Service Agreement Definition
serviceAgreement ATTRIBUTE ::=   { ID sagr    }
-- +++++++++++++++++++++++++++++++++++++
-- Service Package Definition
servicePackage ATTRIBUTE   ::=   { ID spack }
-- +++++++++++++++++++++++++++++++++++++
-- TCF Service Definition
-- The tcf Service Id starts with "tcf" and is
-- followed by the instance number.
tcfService ATTRIBUTE    ::=    { ID tcf     }
-- +++++++++++++++++++++++++++++++++++++
-- TCVA Service Definition
-- The tcva Service Id starts with "tcva" and is
-- followed by the instance number.
tcvaService ATTRIBUTE      ::=   { ID tcva }
END

CCSDS-SLE-TRANSFER-SERVICE-RAF-STRUCTURES
{iso identified-organization(3) standards-producing-organization(112)
     ccsds(4) space-link-extension(3) sle-transfer-services(1)
     modules(1) return-all-frames-service(11) version-five(5)
     asn1-raf-structures(1)}
DEFINITIONS
IMPLICIT TAGS
::= BEGIN
EXPORTS      AntennaId
,            CarrierLockStatus
,            DiagnosticRafGet
,            DiagnosticRafStart
,            FrameQuality
,            FrameSyncLockStatus
,            LockStatus
,            Notification
,            RafGetParameter
,            RafProductionStatus
,            RafParameterName
,            RequestedFrameQuality
,            SymbolLockStatus
;
IMPORTS      DeliveryMode
,            Diagnostics
,            IntPosShort
,            IntPosLong
,            ParameterName
,            Time
     FROM CCSDS-SLE-TRANSFER-SERVICE-COMMON-TYPES
             ReportingCycle
     FROM CCSDS-SLE-TRANSFER-SERVICE-COMMON-PDUS
;
AntennaId                    ::= CHOICE
{    globalForm                       [0] OBJECT IDENTIFIER
,    localForm                        [1] OCTET STRING (SIZE (1 .. 16))
}
CarrierLockStatus     ::=   LockStatus
( inLock
| outOfLock
| unknown
)
CurrentReportingCycle        ::= CHOICE
{    periodicReportingOff             [0] NULL
,    periodicReportingOn              [1] ReportingCycle
}

DiagnosticRafGet            ::= CHOICE
{   common                           [0] Diagnostics
,   specific                         [1] INTEGER
    {   unknownParameter                     (0)
    }
}
DiagnosticRafStart          ::= CHOICE
{   common                           [0] Diagnostics
,   specific                         [1] INTEGER
    {   outOfService                         (0)
    ,   unableToComply                       (1)
    ,   invalidStartTime                     (2)
    ,   invalidStopTime                      (3)
    ,   missingTimeValue                     (4)
    }
}
FrameQuality               ::= INTEGER
{   good                             (0)
,   erred                            (1)
,   undetermined                     (2)
}
FrameSyncLockStatus        ::=   LockStatus
( inLock
| outOfLock
| unknown
)
LockStatus                 ::= INTEGER
{   inLock                           (0)
,   outOfLock                        (1)
,   notInUse                         (2)
,   unknown                          (3)
}
LockStatusReport            ::= SEQUENCE
{   time                             Time
,   carrierLockStatus                CarrierLockStatus
,   subcarrierLockStatus             LockStatus
,   symbolSyncLockStatus             SymbolLockStatus
}
Notification                ::= CHOICE
{   lossFrameSync                    [0] LockStatusReport
,   productionStatusChange           [1] RafProductionStatus
,   excessiveDataBacklog             [2] NULL
,   endOfData                        [3] NULL
}

RafGetParameter      ::= CHOICE
{   parBufferSize            [0] SEQUENCE
    {   parameterName                 ParameterName (bufferSize)
    ,   parameterValue                IntPosShort
                                      -- bufferSize in number of invocations
                                      -- that can be held in buffer
    }
,   parDeliveryMode          [1] SEQUENCE
    {   parameterName                 ParameterName (deliveryMode)
    ,   parameterValue                RafDeliveryMode
    }
,   parLatencyLimit          [2] SEQUENCE
    {   parameterName                 ParameterName (latencyLimit)
    ,   parameterValue                CHOICE
        {    online                   [0] IntPosShort
                                              -- latencyLimit in seconds
        ,    offline                  [1] NULL
        }
    }
,   parMinReportingCycle      [7] SEQUENCE
    {   parameterName                 ParameterName (minReportingCycle)
    ,   parameterValue                IntPosShort (1 .. 600)
    }
,   parPermittedFrameQuality [6] SEQUENCE
    {   parameterName                 ParameterName (permittedFrameQuality)
    ,   parameterValue                PermittedFrameQualitySet
    }
,   parReportingCycle        [3] SEQUENCE
    {   parameterName                 ParameterName (reportingCycle)
    ,   parameterValue                CurrentReportingCycle
    }
,   parReqFrameQuality       [4] SEQUENCE
    {   parameterName                 ParameterName (requestedFrameQuality)
    ,   parameterValue                INTEGER
        {    goodFramesOnly               (0)
        ,    erredFrameOnly               (1)
        ,    allFrames                    (2)
        }
    }
,   parReturnTimeout         [5] SEQUENCE
    {   parameterName                 ParameterName (returnTimeoutPeriod)
    ,   parameterValue                TimeoutPeriod
    }
}
PermittedFrameQualitySet     ::= SET SIZE (1 .. 3) OF RequestedFrameQuality
RafDeliveryMode              ::= DeliveryMode
(   rtnTimelyOnline
|   rtnCompleteOnline
|   rtnOffline
)

RafParameterName            ::= ParameterName
(   bufferSize
|   deliveryMode
|   latencyLimit
|   minReportingCycle
|   permittedFrameQuality
|   reportingCycle
|   requestedFrameQuality
|   returnTimeoutPeriod
)
RafProductionStatus         ::= INTEGER
{   running                          (0)
,   interrupted                      (1)
,   halted                           (2)
}
RequestedFrameQuality       ::= INTEGER
{   goodFramesOnly                   (0)
,   erredFrameOnly                   (1)
,   allFrames                        (2)
}
SymbolLockStatus        ::=   LockStatus
( inLock
| outOfLock
| unknown
)
TimeoutPeriod               ::= INTEGER (1 .. 600)
                                -- measured in seconds
END

CCSDS-SLE-TRANSFER-SERVICE-RAF-INCOMING-PDUS
{iso identified-organization(3) standards-producing-organization(112)
     ccsds(4) space-link-extension(3) sle-transfer-services(1)
     modules(1) return-all-frames-service(11) version-four(4)
     asn1-raf-incoming-pdu(2)}
DEFINITIONS
IMPLICIT TAGS
::= BEGIN
IMPORTS      ConditionalTime
,            Credentials
,            InvokeId
,            ParameterName
     FROM CCSDS-SLE-TRANSFER-SERVICE-COMMON-TYPES
             SleScheduleStatusReportInvocation
,            SleStopInvocation
     FROM CCSDS-SLE-TRANSFER-SERVICE-COMMON-PDUS
             RafParameterName
,            RequestedFrameQuality
     FROM CCSDS-SLE-TRANSFER-SERVICE-RAF-STRUCTURES
             SleBindInvocation
,            SleBindReturn
,            SlePeerAbort
,            SleUnbindInvocation
,            SleUnbindReturn
     FROM CCSDS-SLE-TRANSFER-SERVICE-BIND-TYPES
;
-- =============================================================
-- The first part of the module definition contains the RAF type
-- that contains all the possible PDUs the provider may receive.
-- =============================================================
RafUsertoProviderPdu             ::= CHOICE
{ rafBindInvocation                   [100] SleBindInvocation
, rafBindReturn                       [101] SleBindReturn
, rafUnbindInvocation                 [102] SleUnbindInvocation
, rafUnbindReturn                     [103] SleUnbindReturn
, rafStartInvocation                  [0]    RafStartInvocation
, rafStopInvocation                   [2]    SleStopInvocation
, rafScheduleStatusReportInvocation [4]      SleScheduleStatusReportInvocation
, rafGetParameterInvocation           [6]    RafGetParameterInvocation
, rafPeerAbortInvocation              [104] SlePeerAbort
}
-- =============================================================
-- The second part of the module definition contains the types
-- used by the RAF-PDUs declared in the first part.
-- =============================================================
RafGetParameterInvocation        ::= SEQUENCE
{    invokerCredentials                   Credentials
,    invokeId                             InvokeId
,    rafParameter                         RafParameterName
}

RafStartInvocation           ::= SEQUENCE
{   invokerCredentials                 Credentials
,   invokeId                           InvokeId
,   startTime                          ConditionalTime
,   stopTime                           ConditionalTime
,   requestedFrameQuality              RequestedFrameQuality
}
END

CCSDS-SLE-TRANSFER-SERVICE-RAF-OUTGOING-PDUS
{iso identified-organization(3) standards-producing-organization(112)
     ccsds(4) space-link-extension(3) sle-transfer-services(1)
     modules(1) return-all-frames-service(11) version-four(4)
     asn1-outgoing-pdu(3)}
DEFINITIONS
IMPLICIT TAGS
::= BEGIN
IMPORTS      Credentials
,            IntUnsignedLong
,            InvokeId
,            SpaceLinkDataUnit
,            Time
     FROM CCSDS-SLE-TRANSFER-SERVICE-COMMON-TYPES
             SleAcknowledgement
,            SleScheduleStatusReportReturn
     FROM CCSDS-SLE-TRANSFER-SERVICE-COMMON-PDUS
             AntennaId
,            CarrierLockStatus
,            DiagnosticRafGet
,            DiagnosticRafStart
,            FrameQuality
,            FrameSyncLockStatus
,            LockStatus
,            Notification
,            RafGetParameter
,            RafProductionStatus
,            SymbolLockStatus
     FROM CCSDS-SLE-TRANSFER-SERVICE-RAF-STRUCTURES
             SleBindInvocation
,            SleBindReturn
,            SlePeerAbort
,            SleUnbindInvocation
,            SleUnbindReturn
     FROM CCSDS-SLE-TRANSFER-SERVICE-BIND-TYPES
;
-- =============================================================
-- The first part of the module definition contains the RAF type
-- that contains all the possible PDUs the provider may send.
-- =============================================================
RafProviderToUserPdu         ::= CHOICE
{ rafBindInvocation                   [100]  SleBindInvocation
, rafBindReturn                       [101]  SleBindReturn
, rafUnbindInvocation                 [102]  SleUnbindInvocation
, rafUnbindReturn                     [103]  SleUnbindReturn
, rafStartReturn                      [1]    RafStartReturn
, rafStopReturn                       [3]    SleAcknowledgement
, rafTransferBuffer                   [8]    RafTransferBuffer
, rafScheduleStatusReportReturn       [5]    SleScheduleStatusReportReturn
, rafStatusReportInvocation           [9]    RafStatusReportInvocation
, rafGetParameterReturn               [7]    RafGetParameterReturn
, rafPeerAbortInvocation              [104]  SlePeerAbort
}

-- =============================================================
-- The second part of the module definition contains the types
-- used by the RAF-PDUs declared in the first part.
-- =============================================================
FrameOrNotification             ::= CHOICE
{   annotatedFrame                       [0] RafTransferDataInvocation
,   syncNotification                     [1] RafSyncNotifyInvocation
}

RafGetParameterReturn           ::= SEQUENCE
{   performerCredentials                 Credentials
,   invokeId                             InvokeId
,   result                               CHOICE
    {   positiveResult                       [0] RafGetParameter
    ,   negativeResult                       [1] DiagnosticRafGet
    }
}
RafStartReturn                  ::= SEQUENCE
{   performerCredentials                 Credentials
,   invokeId                             InvokeId
,   result                               CHOICE
    {   positiveResult                       [0] NULL
    ,   negativeResult                       [1] DiagnosticRafStart
    }
}
RafStatusReportInvocation       ::= SEQUENCE
{   invokerCredentials                   Credentials
,   errorFreeFrameNumber                 IntUnsignedLong
,   deliveredFrameNumber                 IntUnsignedLong
,   frameSyncLockStatus                  FrameSyncLockStatus
,   symbolSyncLockStatus                 SymbolLockStatus
,   subcarrierLockStatus                 LockStatus
,   carrierLockStatus                    CarrierLockStatus
,   productionStatus                     RafProductionStatus
}
RafTransferBuffer               ::= SEQUENCE OF FrameOrNotification
RafSyncNotifyInvocation         ::= SEQUENCE
{   invokerCredentials                   Credentials
,   notification                         Notification
}
RafTransferDataInvocation   ::= SEQUENCE
{   invokerCredentials               Credentials
,   earthReceiveTime                 Time
,   antennaId                        AntennaId
,   dataLinkContinuity               INTEGER (-1 .. 16777215)
,   deliveredFrameQuality            FrameQuality
,   privateAnnotation                CHOICE
    {   null                             [0] NULL
    ,   notNull                          [1] OCTET STRING (SIZE (1 .. 128))
    }
,   data                             SpaceLinkDataUnit
}
END
